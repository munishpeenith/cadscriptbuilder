;; Tests every -LAYER option the new blocks will use, on a test layer CSB-T1.
;; CSB_TEST_A = apply everything, CSB_TEST_B = reverse it. Each is one undo (U).

(defun c:CSB_TEST_A ()
  (command "_.UNDO" "_BEGIN")
  (command "_.-LAYER" "_New" "CSB-T1" "")
  (command "_.-LAYER" "_Color" "1" "CSB-T1" "")
  (command "_.-LAYER" "_LWeight" "0.35" "CSB-T1" "")
  (command "_.-LAYER" "_TRansparency" "50" "CSB-T1" "")
  (command "_.-LAYER" "_Description" "CSB test layer" "CSB-T1" "")
  (command "_.-LAYER" "_Plot" "_No" "CSB-T1" "")
  (command "_.-LAYER" "_OFF" "CSB-T1" "")
  (command "_.-LAYER" "_LOck" "CSB-T1" "")
  (command "_.-LAYER" "_Freeze" "CSB-T1" "")
  (command "_.UNDO" "_END")
  (princ "\nCSB_TEST_A done. CSB-T1 should be: red, 0.35, 50% transparent, described, no plot, off, locked, frozen.")
  (princ))

(defun c:CSB_TEST_B ()
  (command "_.UNDO" "_BEGIN")
  (command "_.-LAYER" "_Thaw" "CSB-T1" "")
  (command "_.-LAYER" "_Unlock" "CSB-T1" "")
  (command "_.-LAYER" "_ON" "CSB-T1" "")
  (command "_.-LAYER" "_Plot" "_Plot" "CSB-T1" "")
  (command "_.-LAYER" "_Ltype" "CONTINUOUS" "CSB-T1" "")
  (command "_.-LAYER" "_Set" "CSB-T1" "")
  (princ (strcat "\nCurrent layer is now: " (getvar "CLAYER")))
  (command "_.-LAYER" "_Set" "0" "")
  (command "_.UNDO" "_END")
  (princ "\nCSB_TEST_B done. CSB-T1 should be: thawed, unlocked, on, plots, Continuous. Current layer back to 0.")
  (princ))

(princ "\nLoaded. Type CSB_TEST_A, check the Layer Manager, then CSB_TEST_B.")
(princ)
